string URL = "FARNELL_LINK";

if (board) board(B) {
	B.elements(E) {
		if (E.name == argv[1]){
			if (E.attribute[URL] != ""){
				string http = E.attribute[URL];
				system("cmd.exe /c start " + http );
			}
			else{
				dlgMessageBox("The specified object has no specified Farnell_Link.");
			}
		}
	} 
}

if (schematic) schematic(SCH) {
	SCH.parts(P) {
		if (P.name == argv[1]){
			if (P.attribute[URL] != ""){
				string http = P.attribute[URL];
				system("cmd.exe /c start " + http );
			}
			else{
				dlgMessageBox("The specified object has no specified Farnell_Link.");
			}
		}
	}
}
