/* Launching this script will open the datasheet in a new windows
   This script hasn't been tested a lot.*/


string MEMBER = "DATASHEET";
string DATASHEET_PATH = "../datasheets/";

if (board) board(B) {
	B.elements(E) {
		if (E.name == argv[1]){
			if (E.attribute[MEMBER] != ""){
				string name = E.attribute[MEMBER];
				system("cmd.exe /c start " + DATASHEET_PATH + name );
			}
			else{
				dlgMessageBox("The specified object has no specified Datasheet.");
			}
		}
	} 
}

if (schematic) schematic(SCH) {
	SCH.parts(P) {
		if (P.name == argv[1]){
			if (P.attribute[MEMBER] != ""){
				string name = P.attribute[MEMBER];
				system("cmd.exe /c start " + DATASHEET_PATH + name );
			}
			else{
				dlgMessageBox("The specified object has no specified Datasheet.");
			}
		}
	}
}
